# ISeePricey

# Specification: BusinessRequirements
- Class: Business requirements
- ReqIF.Description: BusinessRequirements

## REQ-23: Client context (BusinessRequirement)
- Kind: ClientContext
- ParamValue: C:\Users\DEV\OneDrive\work\WorkSpy\work\sales\plans\rfp\finalized\ISeePricey.archimate

## REQ-24: Product request (BusinessRequirement)
- Kind: ProductRequest
- ParamValue: /archimate:model/folder[@name='Business']/element[@name='Single page website development']

## REQ-25 (BusinessRequirement)
- Kind: ProductObject
- ParamValue: /archimate:model/folder[@name='Application']/element[@id='ccefaf22-b441-4616-8948-21b608c78218']

# Specification: UserRequirements
- ReqIF.Description: User Requirements

## REQ-8: Content Requirements (Requirement)
Content requirements

## REQ-9: Navigation requirements (Requirement)

# Specification
- ReqIF.Description: Quality-of-Service Requirements

# Specification
- ReqIF.Description: 06.Technology Requirements

# Specification: DesignRequirements
- ReqIF.Description: Design requirements

## REQ-27: Carousel (Requirement)
- Kind: Functional.Feature
- ParamValue: /archimate:model/folder[@name='Application']/folder/element[@name='Carousel']

### REQ-19: CarouselPicture (ParameterRequirement)
Carousel picture
- ParamValue: 1.bmp

### REQ-22: CarouselPicture (ParameterRequirement)
Carousel picture
- ParamValue: 2.bmp

# Specification: DeploymentTemplate
- Class: DeploymentRequirements
- ReqIF.Description: Deployment Requirements

## REQ-28 (Requirement)
- Kind: NonFunctional.Deployment
- ParamValue: /archimate:model/folder[@name='Application']/element[@xsi:type='archimate:ApplicationService']
- ProcessingInstruction: ApplyTemplate

## REQ-10: Deployment platform (Requirement)
GCP

## REQ-13 (ParameterRequirement)
Deployment Platform
- ParamValue: GCP
